PROMETHEUS-TRAPPER-MIB DEFINITIONS ::= BEGIN

IMPORTS
    MODULE-IDENTITY, OBJECT-TYPE, TimeTicks, experimental, NOTIFICATION-TYPE
        FROM SNMPv2-SMI
    DisplayString, TimeStamp
        FROM SNMPv2-TC
;

prometheusTrapper MODULE-IDENTITY
    LAST-UPDATED "201811160000Z"
    ORGANIZATION "DaoCloud"
    CONTACT-INFO "https://github.com/DaoCloud/prometheus_webhook_snmptrapper"
    DESCRIPTION  "Example MIB objects for agent module example implementations"
    REVISION     "201811160000Z"
    DESCRIPTION  "Created MIB"
    ::= { experimental 1977 }

--
-- Top level structure
--
prometheusTrapperNotifications        OBJECT IDENTIFIER ::= { prometheusTrapper 1 }
prometheusTrapperNotificationsPrefix  OBJECT IDENTIFIER ::= { prometheusTrapperNotifications 0 }
prometheusTrapperNotificationObjects  OBJECT IDENTIFIER ::= { prometheusTrapperNotifications 1 }

--
--  Notifications
--

prometheusTrapperNotificationTimestamp OBJECT-TYPE
    SYNTAX      DisplayString
    MAX-ACCESS  accessible-for-notify
    STATUS      current
    DESCRIPTION
        "The time the notification-event occurred."
::= { prometheusTrapperNotificationObjects 1 }

prometheusTrapperNotificationAlert OBJECT-TYPE
    SYNTAX      DisplayString
    MAX-ACCESS  accessible-for-notify
    STATUS      current
    DESCRIPTION
        "The name of the alert."
::= { prometheusTrapperNotificationObjects 2 }

prometheusTrapperNotificationInstance OBJECT-TYPE
    SYNTAX      DisplayString
    MAX-ACCESS  accessible-for-notify
    STATUS      current
    DESCRIPTION
        "Unique identifier for the instance (hostname / instance-id / ip-address etc)."
::= { prometheusTrapperNotificationObjects 3 }

prometheusTrapperNotificationTenant OBJECT-TYPE
    SYNTAX      DisplayString
    MAX-ACCESS  accessible-for-notify
    STATUS      current
    DESCRIPTION
        "The name of tenant. Coordinated with kubernetes namespace"
::= { prometheusTrapperNotificationObjects 4 }

prometheusTrapperNotificationApplication OBJECT-TYPE
    SYNTAX      DisplayString
    MAX-ACCESS  accessible-for-notify
    STATUS      current
    DESCRIPTION
        "The name of DCE application."
::= { prometheusTrapperNotificationObjects 5 }

prometheusTrapperNotificationSeverity OBJECT-TYPE
    SYNTAX      DisplayString
    MAX-ACCESS  accessible-for-notify
    STATUS      current
    DESCRIPTION
        "The severity of the notification."
::= { prometheusTrapperNotificationObjects 6 }

prometheusTrapperNotificationDescription OBJECT-TYPE
    SYNTAX      DisplayString
    MAX-ACCESS  accessible-for-notify
    STATUS      current
    DESCRIPTION
        "Description field."
::= { prometheusTrapperNotificationObjects 7 }


prometheusTrapperFiringNotification NOTIFICATION-TYPE
    OBJECTS     {
                    prometheusTrapperNotificationTimestamp,
                    prometheusTrapperNotificationAlert,
                    prometheusTrapperNotificationInstance,
                    prometheusTrapperNotificationTenant,
                    prometheusTrapperNotificationApplication,
                    prometheusTrapperNotificationSeverity,
                    prometheusTrapperNotificationDescription
                }
    STATUS      current
    DESCRIPTION
        "A notification describing the OCCURRENCE of a Prometheus Alert event."
::= { prometheusTrapperNotificationsPrefix 1 }

prometheusTrapperRecoveryNotification NOTIFICATION-TYPE
    OBJECTS     {
                    prometheusTrapperNotificationTimestamp,
                    prometheusTrapperNotificationAlert,
                    prometheusTrapperNotificationInstance,
                    prometheusTrapperNotificationTenant,
                    prometheusTrapperNotificationApplication,
                    prometheusTrapperNotificationSeverity,
                    prometheusTrapperNotificationDescription
                }
    STATUS      current
    DESCRIPTION
        "A notification describing the RECOVERY of a Prometheus Alert event."
::= { prometheusTrapperNotificationsPrefix 2 }

END
